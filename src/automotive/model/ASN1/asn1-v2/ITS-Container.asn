ITS-Container {
itu-t (0) identified-organization (4) etsi (0) itsDomain (5) wg1 (1) ts (102894) cdd (2) version (1) 
}

DEFINITIONS AUTOMATIC TAGS ::=

BEGIN

ItsPduHeaderV1 ::= SEQUENCE {
	protocolVersion INTEGER{currentVersion(1)} (0..255),
	messageID INTEGER{denm(1),cam(2), poi(3), spat(4), map(5), ivi(6), ev-rsr(7)} (0..255),
	stationID StationIDV1
}

StationIDV1 ::= INTEGER(0..4294967295)

ReferencePositionV1 ::= SEQUENCE {
	latitude LatitudeV1,
	longitude LongitudeV1,
	positionConfidenceEllipse PosConfidenceEllipseV1 ,
	altitude AltitudeV1
}

DeltaReferencePositionV1 ::= SEQUENCE {
	deltaLatitude DeltaLatitudeV1,
	deltaLongitude DeltaLongitudeV1,
	deltaAltitude DeltaAltitudeV1
}

LongitudeV1 ::= INTEGER {oneMicrodegreeEast (10), oneMicrodegreeWest (-10), unavailable(1800000001)} (-1800000000..1800000001)

LatitudeV1 ::= INTEGER {oneMicrodegreeNorth (10), oneMicrodegreeSouth (-10), unavailable(900000001)} (-900000000..900000001)

AltitudeV1 ::= SEQUENCE {
	altitudeValue AltitudeValueV1,
	altitudeConfidence AltitudeConfidenceV1
}

AltitudeValueV1 ::= INTEGER {referenceEllipsoidSurface(0), oneCentimeter(1), unavailable(800001)} (-100000..800001)

AltitudeConfidenceV1 ::= ENUMERATED {
	alt-000-01 (0),
	alt-000-02 (1),
	alt-000-05 (2),
	alt-000-10 (3),
	alt-000-20 (4),
	alt-000-50 (5),
	alt-001-00 (6),
	alt-002-00 (7),
	alt-005-00 (8),
	alt-010-00 (9),
	alt-020-00 (10),
	alt-050-00 (11),
	alt-100-00 (12),
	alt-200-00 (13),
	outOfRange (14),
	unavailable (15)
}

DeltaLongitudeV1 ::= INTEGER {oneMicrodegreeEast (10), oneMicrodegreeWest (-10), unavailable(131072)} (-131071..131072)

DeltaLatitudeV1 ::= INTEGER {oneMicrodegreeNorth (10), oneMicrodegreeSouth (-10) , unavailable(131072)} (-131071..131072)

DeltaAltitudeV1 ::= INTEGER {oneCentimeterUp (1), oneCentimeterDown (-1), unavailable(12800)} (-12700..12800)

PosConfidenceEllipseV1 ::= SEQUENCE {
	semiMajorConfidence SemiAxisLengthV1,
	semiMinorConfidence SemiAxisLengthV1,
	semiMajorOrientation HeadingValueV1
}

PathPointV1 ::= SEQUENCE {
	pathPosition DeltaReferencePositionV1,
	pathDeltaTime PathDeltaTimeV1 OPTIONAL
}

PathDeltaTimeV1 ::= INTEGER {tenMilliSecondsInPast(1)} (1..65535, ...)

PtActivationV1 ::= SEQUENCE {
	ptActivationType PtActivationTypeV1,
	ptActivationData PtActivationDataV1
}

PtActivationTypeV1 ::= INTEGER {undefinedCodingType(0), r09-16CodingType(1), vdv-50149CodingType(2)} (0..255)

PtActivationDataV1 ::= OCTET STRING (SIZE(1..20))

AccelerationControlV1 ::= BIT STRING {
	brakePedalEngaged (0),
	gasPedalEngaged (1),
	emergencyBrakeEngaged (2),
	collisionWarningEngaged (3),
	accEngaged (4),
	cruiseControlEngaged (5),
	speedLimiterEngaged (6)
} (SIZE(7))


SemiAxisLengthV1 ::= INTEGER{oneCentimeter(1), outOfRange(4094), unavailable(4095)} (0..4095)

CauseCodeV1 ::= SEQUENCE {
	causeCode CauseCodeTypeV1,
	subCauseCode SubCauseCodeTypeV1
}

CauseCodeTypeV1 ::= INTEGER {
	reserved (0),
	trafficCondition (1),
	accident (2),
	roadworks (3),
	adverseWeatherCondition-Adhesion (6),
	hazardousLocation-SurfaceCondition (9),
	hazardousLocation-ObstacleOnTheRoad (10),
	hazardousLocation-AnimalOnTheRoad (11),
	humanPresenceOnTheRoad (12),
	wrongWayDriving (14),
	rescueAndRecoveryWorkInProgress (15),
	adverseWeatherCondition-ExtremeWeatherCondition (17),
	adverseWeatherCondition-Visibility (18),
	adverseWeatherCondition-Precipitation (19),
	slowVehicle (26),
	dangerousEndOfQueue (27),
	vehicleBreakdown (91),
	postCrash (92),
	humanProblem (93),
	stationaryVehicle (94),
	emergencyVehicleApproaching (95),
	hazardousLocation-DangerousCurve (96),
	collisionRisk (97),
	signalViolation (98),
	dangerousSituation (99)
} (0..255)

SubCauseCodeTypeV1 ::= INTEGER (0..255)

TrafficConditionSubCauseCodeV1 ::= INTEGER {unavailable(0), increasedVolumeOfTraffic(1), trafficJamSlowlyIncreasing(2), trafficJamIncreasing(3), trafficJamStronglyIncreasing(4), trafficStationary(5), trafficJamSlightlyDecreasing(6), trafficJamDecreasing(7), trafficJamStronglyDecreasing(8)} (0..255)

AccidentSubCauseCodeV1 ::= INTEGER {unavailable(0), multiVehicleAccident(1), heavyAccident(2), accidentInvolvingLorry(3), accidentInvolvingBus(4), accidentInvolvingHazardousMaterials(5), accidentOnOppositeLane(6), unsecuredAccident(7), assistanceRequested(8)} (0..255)

RoadworksSubCauseCodeV1 ::= INTEGER {unavailable(0), majorRoadworks(1), roadMarkingWork(2), slowMovingRoadMaintenance(3), shortTermStationaryRoadworks(4), streetCleaning(5), winterService(6)} (0..255)

HumanPresenceOnTheRoadSubCauseCodeV1 ::= INTEGER {unavailable(0), childrenOnRoadway(1), cyclistOnRoadway(2), motorcyclistOnRoadway(3)} (0..255)

WrongWayDrivingSubCauseCodeV1 ::= INTEGER {unavailable(0), wrongLane(1), wrongDirection(2)} (0..255)

AdverseWeatherCondition-ExtremeWeatherConditionSubCauseCodeV1 ::= INTEGER {unavailable(0), strongWinds(1), damagingHail(2), hurricane(3), thunderstorm(4), tornado(5), blizzard(6)} (0..255)

AdverseWeatherCondition-AdhesionSubCauseCodeV1 ::= INTEGER {unavailable(0), heavyFrostOnRoad(1), fuelOnRoad(2), mudOnRoad(3), snowOnRoad(4), iceOnRoad(5), blackIceOnRoad(6), oilOnRoad(7), looseChippings(8), instantBlackIce(9), roadsSalted(10)} (0..255)

AdverseWeatherCondition-VisibilitySubCauseCodeV1 ::= INTEGER {unavailable(0), fog(1), smoke(2), heavySnowfall(3), heavyRain(4), heavyHail(5), lowSunGlare(6), sandstorms(7), swarmsOfInsects(8)} (0..255)

AdverseWeatherCondition-PrecipitationSubCauseCodeV1 ::= INTEGER {unavailable(0), heavyRain(1), heavySnowfall(2), softHail(3)} (0..255)

SlowVehicleSubCauseCodeV1 ::= INTEGER {unavailable(0), maintenanceVehicle(1), vehiclesSlowingToLookAtAccident(2), abnormalLoad(3), abnormalWideLoad(4), convoy(5), snowplough(6), deicing(7), saltingVehicles(8)} (0..255)
 
StationaryVehicleSubCauseCodeV1 ::= INTEGER {unavailable(0), humanProblem(1), vehicleBreakdown(2), postCrash(3), publicTransportStop(4), carryingDangerousGoods(5)} (0..255)

HumanProblemSubCauseCodeV1 ::= INTEGER {unavailable(0), glycemiaProblem(1), heartProblem(2)} (0..255)

EmergencyVehicleApproachingSubCauseCodeV1 ::= INTEGER {unavailable(0), emergencyVehicleApproaching(1), prioritizedVehicleApproaching(2)} (0..255)

HazardousLocation-DangerousCurveSubCauseCodeV1 ::= INTEGER {unavailable(0), dangerousLeftTurnCurve(1), dangerousRightTurnCurve(2), multipleCurvesStartingWithUnknownTurningDirection(3), multipleCurvesStartingWithLeftTurn(4), multipleCurvesStartingWithRightTurn(5)} (0..255)

HazardousLocation-SurfaceConditionSubCauseCodeV1 ::= INTEGER {unavailable(0), rockfalls(1), earthquakeDamage(2), sewerCollapse(3), subsidence(4), snowDrifts(5), stormDamage(6), burstPipe(7), volcanoEruption(8), fallingIce(9)} (0..255)

HazardousLocation-ObstacleOnTheRoadSubCauseCodeV1 ::= INTEGER {unavailable(0), shedLoad(1), partsOfVehicles(2), partsOfTyres(3), bigObjects(4), fallenTrees(5), hubCaps(6), waitingVehicles(7)} (0..255)

HazardousLocation-AnimalOnTheRoadSubCauseCodeV1 ::= INTEGER {unavailable(0), wildAnimals(1), herdOfAnimals(2), smallAnimals(3), largeAnimals(4)} (0..255)

 CollisionRiskSubCauseCodeV1 ::= INTEGER {unavailable(0), longitudinalCollisionRisk(1), crossingCollisionRisk(2), lateralCollisionRisk(3), vulnerableRoadUser(4)} (0..255)
 
 SignalViolationSubCauseCodeV1 ::= INTEGER {unavailable(0), stopSignViolation(1), trafficLightViolation(2), turningRegulationViolation(3)} (0..255)

RescueAndRecoveryWorkInProgressSubCauseCodeV1 ::= INTEGER {unavailable(0), emergencyVehicles(1), rescueHelicopterLanding(2), policeActivityOngoing(3), medicalEmergencyOngoing(4), childAbductionInProgress(5)} (0..255)

DangerousEndOfQueueSubCauseCodeV1 ::= INTEGER {unavailable(0), suddenEndOfQueue(1), queueOverHill(2), queueAroundBend(3), queueInTunnel(4)} (0..255)

DangerousSituationSubCauseCodeV1 ::= INTEGER {unavailable(0), emergencyElectronicBrakeEngaged(1), preCrashSystemEngaged(2), espEngaged(3), absEngaged(4), aebEngaged(5), brakeWarningEngaged(6), collisionRiskWarningEngaged(7)} (0..255)

VehicleBreakdownSubCauseCodeV1 ::= INTEGER {unavailable(0), lackOfFuel (1), lackOfBatteryPower (2), engineProblem(3), transmissionProblem(4), engineCoolingProblem(5), brakingSystemProblem(6), steeringProblem(7), tyrePuncture(8)} (0..255)

PostCrashSubCauseCodeV1 ::= INTEGER {unavailable(0), accidentWithoutECallTriggered (1), accidentWithECallManuallyTriggered (2), accidentWithECallAutomaticallyTriggered (3), accidentWithECallTriggeredWithoutAccessToCellularNetwork(4)} (0..255)

CurvatureV1 ::= SEQUENCE {
 curvatureValue CurvatureValueV1,
 curvatureConfidence CurvatureConfidenceV1
}

CurvatureValueV1 ::= INTEGER {straight(0), reciprocalOf1MeterRadiusToRight(-30000), reciprocalOf1MeterRadiusToLeft(30000), unavailable(30001)} (-30000..30001)

CurvatureConfidenceV1 ::= ENUMERATED {
	onePerMeter-0-00002 (0),
	onePerMeter-0-0001 (1),
	onePerMeter-0-0005 (2),
	onePerMeter-0-002 (3),
	onePerMeter-0-01 (4),
	onePerMeter-0-1 (5),
	outOfRange (6),
	unavailable (7)
}

CurvatureCalculationModeV1::= ENUMERATED {yawRateUsed(0), yawRateNotUsed(1), unavailable(2), ...}

HeadingV1 ::= SEQUENCE {
	headingValue HeadingValueV1,
	headingConfidence HeadingConfidenceV1
}

HeadingValueV1 ::= INTEGER {wgs84North(0), wgs84East(900), wgs84South(1800), wgs84West(2700), unavailable(3601)} (0..3601)

HeadingConfidenceV1 ::= INTEGER {equalOrWithinZeroPointOneDegree (1), equalOrWithinOneDegree (10), outOfRange(126), unavailable(127)} (1..127)

LanePositionV1::= INTEGER {offTheRoad(-1), hardShoulder(0),
outermostDrivingLane(1), secondLaneFromOutside(2)} (-1..14)

ClosedLanesV1 ::= SEQUENCE {
	hardShoulderStatus HardShoulderStatusV1 OPTIONAL,
	drivingLaneStatus DrivingLaneStatusV1,
	...
}

HardShoulderStatusV1 ::= ENUMERATED {availableForStopping(0), closed(1), availableForDriving(2)}

DrivingLaneStatusV1 ::= BIT STRING {outermostLaneClosed(1), secondLaneFromOutsideClosed(2)} (SIZE (1..14))


PerformanceClassV1 ::= INTEGER {unavailable(0), performanceClassA(1), performanceClassB(2)} (0..7)

SpeedValueV1 ::= INTEGER {standstill(0), oneCentimeterPerSec(1), unavailable(16383)} (0..16383)

SpeedConfidenceV1 ::= INTEGER {equalOrWithinOneCentimeterPerSec(1), equalOrWithinOneMeterPerSec(100), outOfRange(126), unavailable(127)} (1..127)

VehicleMassV1 ::= INTEGER {hundredKg(1), unavailable(1024)} (1..1024) 

SpeedV1 ::= SEQUENCE {
	speedValue SpeedValueV1,
	speedConfidence SpeedConfidenceV1
}

DriveDirectionV1 ::= ENUMERATED {forward (0), backward (1), unavailable (2)}

EmbarkationStatusV1 ::= BOOLEAN

LongitudinalAccelerationV1 ::= SEQUENCE {
	longitudinalAccelerationValue LongitudinalAccelerationValueV1,
	longitudinalAccelerationConfidence AccelerationConfidenceV1
}

LongitudinalAccelerationValueV1 ::= INTEGER {pointOneMeterPerSecSquaredForward(1), pointOneMeterPerSecSquaredBackward(-1), unavailable(161)} (-160 .. 161)

AccelerationConfidenceV1 ::= INTEGER {pointOneMeterPerSecSquared(1), outOfRange(101), unavailable(102)} (0 .. 102)

LateralAccelerationV1 ::= SEQUENCE {
	lateralAccelerationValue LateralAccelerationValueV1,
	lateralAccelerationConfidence AccelerationConfidenceV1
}

LateralAccelerationValueV1 ::= INTEGER {pointOneMeterPerSecSquaredToRight(-1), pointOneMeterPerSecSquaredToLeft(1), unavailable(161)} (-160 .. 161)

VerticalAccelerationV1 ::= SEQUENCE {
	verticalAccelerationValue VerticalAccelerationValueV1,
	verticalAccelerationConfidence AccelerationConfidenceV1
}

VerticalAccelerationValueV1 ::= INTEGER {pointOneMeterPerSecSquaredUp(1), pointOneMeterPerSecSquaredDown(-1), unavailable(161)} (-160 .. 161)

StationTypeV1 ::= INTEGER {unknown(0), pedestrian(1), cyclist(2), moped(3), motorcycle(4), passengerCar(5), bus(6), 
lightTruck(7), heavyTruck(8), trailer(9), specialVehicles(10), tram(11), roadSideUnit(15)} (0..255)

ExteriorLightsV1 ::= BIT STRING {
	lowBeamHeadlightsOn      (0),
	highBeamHeadlightsOn     (1),
	leftTurnSignalOn         (2),
	rightTurnSignalOn        (3),
	daytimeRunningLightsOn   (4),
	reverseLightOn           (5),
	fogLightOn               (6),
	parkingLightsOn          (7)
} (SIZE(8))

DangerousGoodsBasicV1::= ENUMERATED {
	explosives1(0),
	explosives2(1),
	explosives3(2),
	explosives4(3),
	explosives5(4),
	explosives6(5),
	flammableGases(6),
	nonFlammableGases(7),
	toxicGases(8),
	flammableLiquids(9),
	flammableSolids(10),
	substancesLiableToSpontaneousCombustion(11),
	substancesEmittingFlammableGasesUponContactWithWater(12),
	oxidizingSubstances(13),
	organicPeroxides(14),
	toxicSubstances(15),
	infectiousSubstances(16),
	radioactiveMaterial(17),
	corrosiveSubstances(18),
	miscellaneousDangerousSubstances(19)
}

DangerousGoodsExtendedV1 ::= SEQUENCE {
	dangerousGoodsType DangerousGoodsBasicV1,
	unNumber INTEGER (0..9999),
	elevatedTemperature BOOLEAN,
	tunnelsRestricted BOOLEAN,
	limitedQuantity BOOLEAN,
	emergencyActionCode IA5String (SIZE (1..24)) OPTIONAL,
	phoneNumber IA5String (SIZE (1..24)) OPTIONAL,
	companyName UTF8String (SIZE (1..24)) OPTIONAL
}

SpecialTransportTypeV1 ::= BIT STRING {heavyLoad(0), excessWidth(1), excessLength(2), excessHeight(3)} (SIZE(4))

LightBarSirenInUseV1 ::= BIT STRING {
	lightBarActivated (0),
	sirenActivated (1)
} (SIZE(2))

HeightLonCarrV1 ::= INTEGER {oneCentimeter(1), unavailable(100)} (1..100)

PosLonCarrV1 ::= INTEGER {oneCentimeter(1), unavailable(127)} (1..127)

PosPillarV1 ::= INTEGER {tenCentimeters(1), unavailable(30)} (1..30)

PosCentMassV1 ::= INTEGER {tenCentimeters(1), unavailable(63)} (1..63)

RequestResponseIndicationV1 ::= ENUMERATED {request(0), response(1)}

SpeedLimitV1 ::= INTEGER {oneKmPerHour(1)} (1..255)

StationarySinceV1 ::= ENUMERATED {lessThan1Minute(0), lessThan2Minutes(1), lessThan15Minutes(2), equalOrGreater15Minutes(3)}

TemperatureV1 ::= INTEGER {equalOrSmallerThanMinus60Deg (-60), oneDegreeCelsius(1), equalOrGreaterThan67Deg(67)} (-60..67)

TrafficRuleV1 ::= ENUMERATED {noPassing(0), noPassingForTrucks(1), passToRight(2), passToLeft(3), ...
}

WheelBaseVehicleV1 ::= INTEGER {tenCentimeters(1), unavailable(127)} (1..127)

TurningRadiusV1 ::= INTEGER {point4Meters(1), unavailable(255)} (1..255)

PosFrontAxV1 ::= INTEGER {tenCentimeters(1), unavailable(20)} (1..20)

PositionOfOccupantsV1 ::= BIT STRING {
	row1LeftOccupied (0),
	row1RightOccupied (1),
	row1MidOccupied (2),
	row1NotDetectable (3),
	row1NotPresent (4),
	row2LeftOccupied (5),
	row2RightOccupied (6),
	row2MidOccupied (7),
	row2NotDetectable (8),
	row2NotPresent (9),
	row3LeftOccupied (10),
	row3RightOccupied (11),
	row3MidOccupied (12),
	row3NotDetectable (13),
	row3NotPresent (14),
	row4LeftOccupied (15),
	row4RightOccupied (16),
	row4MidOccupied (17),
	row4NotDetectable (18),
	row4NotPresent (19)} (SIZE(20))

PositioningSolutionTypeV1 ::= ENUMERATED {noPositioningSolution(0), sGNSS(1), dGNSS(2), sGNSSplusDR(3), dGNSSplusDR(4), dR(5), ...}

VehicleIdentificationV1 ::= SEQUENCE {
	wMInumber WMInumberV1 OPTIONAL,
	vDS VDSV1 OPTIONAL,
	...
}

WMInumberV1 ::= IA5String (SIZE(1..3))

VDSV1 ::= IA5String (SIZE(6))

EnergyStorageTypeV1 ::= BIT STRING {hydrogenStorage(0), electricEnergyStorage(1), liquidPropaneGas(2), compressedNaturalGas(3), diesel(4), gasoline(5), ammonia(6)} (SIZE(7))

VehicleLengthV1 ::= SEQUENCE {
	vehicleLengthValue VehicleLengthValueV1,
	vehicleLengthConfidenceIndication VehicleLengthConfidenceIndicationV1
}

VehicleLengthValueV1 ::= INTEGER {tenCentimeters(1), outOfRange(1022), unavailable(1023)}  (1..1023)

VehicleLengthConfidenceIndicationV1 ::= ENUMERATED {noTrailerPresent(0), trailerPresentWithKnownLength(1), trailerPresentWithUnknownLength(2), trailerPresenceIsUnknown(3), unavailable(4)}

VehicleWidthV1 ::= INTEGER {tenCentimeters(1), outOfRange(61), unavailable(62)} (1..62)

PathHistoryV1::= SEQUENCE (SIZE(0..40)) OF PathPointV1

EmergencyPriorityV1 ::= BIT STRING {requestForRightOfWay(0), requestForFreeCrossingAtATrafficLight(1)} (SIZE(2))

InformationQualityV1 ::= INTEGER {unavailable(0), lowest(1), highest(7)} (0..7)

RoadTypeV1 ::= ENUMERATED {
	urban-NoStructuralSeparationToOppositeLanes(0),
	urban-WithStructuralSeparationToOppositeLanes(1),
	nonUrban-NoStructuralSeparationToOppositeLanes(2),
	nonUrban-WithStructuralSeparationToOppositeLanes(3)}

SteeringWheelAngleV1 ::= SEQUENCE {
	steeringWheelAngleValue SteeringWheelAngleValueV1,
	steeringWheelAngleConfidence SteeringWheelAngleConfidenceV1
}

SteeringWheelAngleValueV1 ::= INTEGER {straight(0), onePointFiveDegreesToRight(-1), onePointFiveDegreesToLeft(1), unavailable(512)} (-511..512)

SteeringWheelAngleConfidenceV1 ::= INTEGER {equalOrWithinOnePointFiveDegree (1), outOfRange(126), unavailable(127)} (1..127)

TimestampItsV1 ::= INTEGER {utcStartOf2004(0), oneMillisecAfterUTCStartOf2004(1)} (0..4398046511103)

VehicleRoleV1 ::= ENUMERATED {default(0), publicTransport(1), specialTransport(2), dangerousGoods(3), roadWork(4), rescue(5), emergency(6), safetyCar(7), agriculture(8),commercial(9),military(10),roadOperator(11),taxi(12), reserved1(13), reserved2(14), reserved3(15)}

YawRateV1::= SEQUENCE {
	yawRateValue YawRateValueV1,
	yawRateConfidence YawRateConfidenceV1
}

YawRateValueV1 ::= INTEGER {straight(0), degSec-000-01ToRight(-1), degSec-000-01ToLeft(1), unavailable(32767)} (-32766..32767)

YawRateConfidenceV1 ::= ENUMERATED {
	degSec-000-01 (0),
	degSec-000-05 (1),
	degSec-000-10 (2),
	degSec-001-00 (3),
	degSec-005-00 (4),
	degSec-010-00 (5),
	degSec-100-00 (6),
	outOfRange (7),
	unavailable (8)
}

ProtectedZoneTypeV1::=  ENUMERATED {
	cenDsrcTolling (0),
	...
}

RelevanceDistanceV1 ::= ENUMERATED {lessThan50m(0), lessThan100m(1), lessThan200m(2), lessThan500m(3), lessThan1000m(4), lessThan5km(5), lessThan10km(6), over10km(7)}

RelevanceTrafficDirectionV1 ::= ENUMERATED {allTrafficDirections(0), upstreamTraffic(1), downstreamTraffic(2), oppositeTraffic(3)}

TransmissionIntervalV1 ::= INTEGER {oneMilliSecond(1), tenSeconds(10000)} (1..10000)

ValidityDurationV1 ::=	INTEGER {timeOfDetection(0), oneSecondAfterDetection(1)} (0..86400)

ActionIDV1 ::= SEQUENCE {
	originatingStationID StationIDV1,
	sequenceNumber SequenceNumberV1
}

ItineraryPathV1 ::= SEQUENCE SIZE(1..40) OF ReferencePositionV1

ProtectedCommunicationZoneV1 ::= SEQUENCE {
	protectedZoneType		ProtectedZoneTypeV1,
	expiryTime TimestampItsV1 OPTIONAL,
	protectedZoneLatitude	LatitudeV1,
	protectedZoneLongitude	LongitudeV1,
	protectedZoneRadius	ProtectedZoneRadiusV1 OPTIONAL,
	protectedZoneID	ProtectedZoneIDV1 OPTIONAL
}

TracesV1 ::= SEQUENCE SIZE(1..7) OF PathHistoryV1

NumberOfOccupantsV1 ::= INTEGER {oneOccupant (1), unavailable(127)} (0 .. 127)

SequenceNumberV1 ::=	INTEGER (0..65535)

PositionOfPillarsV1 ::= SEQUENCE (SIZE(1..3, ...)) OF PosPillarV1

RestrictedTypesV1 ::= SEQUENCE (SIZE(1..3, ...)) OF StationTypeV1

EventHistoryV1::= SEQUENCE (SIZE(1..23)) OF EventPointV1

EventPointV1 ::= SEQUENCE {
	eventPosition DeltaReferencePositionV1,
	eventDeltaTime PathDeltaTimeV1 OPTIONAL,
	informationQuality InformationQualityV1
}

ProtectedCommunicationZonesRSUV1 ::= SEQUENCE (SIZE(1..16)) OF ProtectedCommunicationZoneV1 



CenDsrcTollingZoneV1 ::= SEQUENCE {
	protectedZoneLatitude LatitudeV1,
	protectedZoneLongitude LongitudeV1,
	cenDsrcTollingZoneID CenDsrcTollingZoneIDV1 OPTIONAL
}

ProtectedZoneRadiusV1 ::= INTEGER {oneMeter(1)} (1..255,...)

ProtectedZoneIDV1 ::= INTEGER (0.. 134217727)

CenDsrcTollingZoneIDV1 ::= ProtectedZoneIDV1

END
